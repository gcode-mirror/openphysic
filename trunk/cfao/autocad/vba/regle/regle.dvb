Attribute VB_Name = "ThisDrawing"
Attribute VB_Base = "0{8E75D913-3D21-11D2-85C4-080009A0C626}"
Attribute VB_Creatable = False
Attribute VB_PredeclaredId = True
Attribute VB_Exposed = True
Attribute VB_TemplateDerived = False
Attribute VB_Customizable = True
Option Explicit

Const PI = 3.14159265358979

'Dim AcadApp As Object 'On crée une variable nommée AcadApp de type Object (AutoCAD ver<2000)

Dim startPoint(0 To 2) As Double
Dim endPoint(0 To 2) As Double
Dim origin(0 To 2) As Double

Dim longueur As Double
Dim largeur As Double
Dim decalage_x As Double


Public Sub Tracer()
Initialiser
'CreerCalques
TracerContour
TracerGraduations
TracerMarques
End Sub

Private Sub Initialiser()
'ThisDrawing.New

longueur = 200#  'mm
largeur = 40#  'mm
decalage_x = 10#  'mm

origin(0) = 0#: origin(1) = 0#: origin(2) = 0#
startPoint(0) = 0#: startPoint(1) = 0#: startPoint(2) = 0#
endPoint(0) = 0#: endPoint(1) = 0#: endPoint(2) = 0#
'TODO
End Sub


Private Sub CreerCalques()
' Creation des calques
'Dim BaCalque As AcadLayer
'Set BaCalque = ThisDrawing.Layers.Item("Plan03") ' Choix du calque
'ThisDrawing.ActiveLayer = BaCalque ' Le calque est rendu courant
End Sub

Private Sub TracerContour()
    'Initialisation des variables
    Dim contour As Object               ' Nom de la variable objet Quadrilatere
    Dim PtSommet(0 To 9) As Double      ' Sommets du quadrilatere
             
    'Donnees
    PtSommet(0) = 0#           ' Coordonnee en X du premier point
    PtSommet(1) = 0#           ' Coordonnee en Y du premier point
    
    PtSommet(2) = longueur + 2 * decalage_x#      ' Coordonnee en X du 2ème point
    PtSommet(3) = 0#           ' Coordonnee en Y du 2ème point
    
    PtSommet(4) = PtSommet(2)  ' Coordonnee en X du 3ème point
    PtSommet(5) = largeur      ' Coordonnee en Y du 3ème point
    
    PtSommet(6) = 0#           ' Coordonnee en X du 4ème point
    PtSommet(7) = PtSommet(5)  ' Coordonnee en Y du 4ème point
    
    PtSommet(8) = 0#           ' Coordonnee en X du premier point pour clore
    PtSommet(9) = 0#           ' Coordonnee en Y du premier point pour clore
               
    'Creation du quadrilatere
    Set contour = ThisDrawing.ModelSpace.AddLightWeightPolyline(PtSommet)
    contour.Closed = True
    contour.Update              ' Mise a jour de l'affichage
End Sub


Private Sub TracerGraduations()
'    AcadApp = GetObject(, "AutoCAD.Application")  'On récupère l'objet Application (AutoCAD ver<2000)
Dim ObjetPolyligne As AcadPolyline
Dim lineObj As AcadLine

Dim i As Integer

Dim insPoint(0 To 2) As Double
Dim textHeight As Double
Dim textStr As String
Dim textObj As AcadText


' Graduations du haut 1cm
startPoint(0) = decalage_x: startPoint(1) = largeur: startPoint(2) = 0#
endPoint(0) = decalage_x: endPoint(1) = largeur - 5#: endPoint(2) = 0#
For i = 0 To 20
    Set lineObj = ThisDrawing.ModelSpace.AddLine(startPoint, endPoint)

    insPoint(0) = startPoint(0)
    insPoint(1) = largeur - 10
    insPoint(2) = 0
    textHeight = 2
    textStr = CInt(i)
    Set textObj = ThisDrawing.ModelSpace.AddText(textStr, insPoint, textHeight)
    textObj.Alignment = acAlignmentCenter
    textObj.Move origin, insPoint
    
    startPoint(0) = startPoint(0) + 10
    endPoint(0) = endPoint(0) + 10
Next i

' Graduations du haut 5mm
startPoint(0) = decalage_x: startPoint(1) = largeur: startPoint(2) = 0#
endPoint(0) = decalage_x: endPoint(1) = largeur - 4#: endPoint(2) = 0#
For i = 0 To 40
    Set lineObj = ThisDrawing.ModelSpace.AddLine(startPoint, endPoint)
    startPoint(0) = startPoint(0) + 5
    endPoint(0) = endPoint(0) + 5
Next i

' Graduations du haut 1mm
startPoint(0) = decalage_x: startPoint(1) = largeur: startPoint(2) = 0#
endPoint(0) = decalage_x: endPoint(1) = largeur - 3#: endPoint(2) = 0#
For i = 0 To 200
    Set lineObj = ThisDrawing.ModelSpace.AddLine(startPoint, endPoint)
    startPoint(0) = startPoint(0) + 1
    endPoint(0) = endPoint(0) + 1
Next i




' Graduations du bas 1cm
startPoint(0) = decalage_x + longueur: startPoint(1) = 0: startPoint(2) = 0#
endPoint(0) = decalage_x + longueur: endPoint(1) = 6#: endPoint(2) = 0#
For i = 0 To 20
    Set lineObj = ThisDrawing.ModelSpace.AddLine(startPoint, endPoint)
    
    insPoint(0) = startPoint(0)
    insPoint(1) = 10
    insPoint(2) = 0
    textHeight = 2
    textStr = CInt(i)
    'textObj.Alignment = acAlignmentCenter
    Set textObj = ThisDrawing.ModelSpace.AddText(textStr, insPoint, textHeight)
    textObj.Rotate insPoint, PI
    textObj.Alignment = acAlignmentCenter
    textObj.Move origin, insPoint

        
    startPoint(0) = startPoint(0) - 10
    endPoint(0) = endPoint(0) - 10
    
Next i

' Graduations du bas 5mm
startPoint(0) = decalage_x + longueur: startPoint(1) = 0: startPoint(2) = 0#
endPoint(0) = decalage_x + longueur: endPoint(1) = 5#: endPoint(2) = 0#
For i = 0 To 40
    Set lineObj = ThisDrawing.ModelSpace.AddLine(startPoint, endPoint)
    startPoint(0) = startPoint(0) - 5
    endPoint(0) = endPoint(0) - 5
Next i

' Graduations du bas 1mm
startPoint(0) = decalage_x + longueur: startPoint(1) = 0: startPoint(2) = 0#
endPoint(0) = decalage_x + longueur: endPoint(1) = 4#: endPoint(2) = 0#
For i = 0 To 200
    Set lineObj = ThisDrawing.ModelSpace.AddLine(startPoint, endPoint)
    startPoint(0) = startPoint(0) - 1
    endPoint(0) = endPoint(0) - 1
Next i

' Graduations du bas 0.5mm
startPoint(0) = decalage_x + longueur: startPoint(1) = 0: startPoint(2) = 0#
endPoint(0) = decalage_x + longueur: endPoint(1) = 2#: endPoint(2) = 0#
For i = 0 To 400
    Set lineObj = ThisDrawing.ModelSpace.AddLine(startPoint, endPoint)
    startPoint(0) = startPoint(0) - 0.5
    endPoint(0) = endPoint(0) - 0.5
Next i


End Sub


Private Sub TracerMarques()

' S. CELLES

Dim insPoint(0 To 2) As Double
Dim textHeight As Double
Dim textStr As String
Dim textObj1 As AcadText
Dim textObj2 As AcadText

insPoint(0) = longueur + decalage_x - largeur / 2
insPoint(1) = largeur / 2
insPoint(2) = 0

textHeight = 4
textStr = "S. CELLES"

Set textObj1 = ThisDrawing.ModelSpace.AddText(textStr, insPoint, textHeight)
textObj1.Alignment = acAlignmentCenter
textObj1.Move origin, insPoint


' MADE IN FRANCE

insPoint(0) = longueur + decalage_x - largeur / 2
insPoint(1) = largeur / 2 - 5
insPoint(2) = 0

textHeight = 2
textStr = "MADE IN FRANCE"


Set textObj2 = ThisDrawing.ModelSpace.AddText(textStr, insPoint, textHeight)
textObj2.Alignment = acAlignmentCenter
textObj2.Move origin, insPoint

' Trou

Dim trou As AcadCircle
Dim PtCentre(0 To 2) As Double   ' Les variables definies comme des nombres
Dim LgRayon As Double            ' a virgule flottante en double precision

'Donnees
PtCentre(0) = 10#
PtCentre(1) = largeur / 2
PtCentre(2) = 0#
                
LgRayon = 2.5
                 
Set trou = ThisDrawing.ModelSpace.AddCircle(PtCentre, LgRayon)
 

End Sub


' TODO
'  Sauver
'   ThisDrawing.SaveAs ("Hello.dwg")
